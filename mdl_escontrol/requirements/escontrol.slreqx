# escontrol

## #1: Output bounding (Functional)
The ES controller output shall be bounded.
- Rationale: Ensures plant actuator input levels are not violated.

### #2: Upper bounding (Functional)
The ES controller output shall be upper bounded.

### #3: Lower bounding (Functional)
The ES controller output shall be lower bounded.

## #4: Parameters (Functional)
Parameters shall be user-defined.

## #5: Carrier signal (Functional)
The carrier signal for modulation and demodulation shall be sinusoidal.

## #7: Parameter mapping (Functional)
Instances if the controller shall be mapped to a dedicated parameter set.
